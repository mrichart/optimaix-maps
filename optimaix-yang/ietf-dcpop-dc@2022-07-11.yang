module ietf-dcpop-dc {
  yang-version 1.1;
  namespace "urn:ietf:params:xml:ns:yang:ietf-dcpop-dc";
  prefix dcpop-dc;

  /* Import inet-types */

  import ietf-inet-types {
    prefix inet;
    reference
      "RFC 6991: Common YANG Data Types";
  }

  /* Import network */

  import ietf-network {
    prefix nw;
    reference
      "RFC 8345: A YANG Data Model for Network Topologies";
  }

  /* Import network topology */

  import ietf-network-topology {
    prefix nt;
    reference
      "RFC 8345: A YANG Data Model for Network Topologies";
  }

  /* Import TE Common types */

  import ietf-te-types {
    prefix te-types;
    reference
      "RFC 8776: Common YANG Data Types for Traffic Engineering";
  }

  /* Import TE Topology */

  import ietf-te-topology {
    prefix tet;
    reference
      "RFC 8795: YANG Data Model for Traffic Engineering (TE)
       Topologies";
  }

  import ietf-vn {
    prefix actn-vn;
    reference
      "Draft-ietf-teas-actn-vn-yang-16: YANG module for the VN";
  }

 organization
    "IETF Traffic Engineering Architecture and Signaling (TEAS)
     Working Group";
  contact
    "WG Web:  <https://tools.ietf.org/wg/teas/>
     WG List:  <mailto:teas@ietf.org>
     Editor: Young Lee <younglee.tx@gmail.com>
           : Dhruv Dhody <dhruv.ietf@gmail.com>";
  description
    "This module contains a YANG module for ...

     Copyright (c) 2020 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX; see the
     RFC itself for full legal notices.

     The keywords 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

 revision 2022-11-16 {
    description
      "initial version.";
    reference
      "RFC XXXX: A YANG Data Model for  ";
  }

  /* Features */




  /* Identity ...*/



  /* Typedef */

 typedef dc-id {
    type string;
    description
      "Defines a type of datacenter (dc) identifier.";
  }


/* Groupings */

 grouping datacenter {
    description
      "Datacenter related information";
    leaf dc-id {
      type dc-id;
      description
        "A unique identifier for the referred datacenter";
    }

leaf-list ap {
      type leafref {
        path "/actn-vn:access-point/actn-vn:ap/actn-vn:ap-id";
      }
      description
        "A reference to the PE node in the native TE Topology";
    }


  } //datacenter


/* Configuration data nodes */

  container dcpop {
    description
      "DC configurations";
    list dc {
      key "dc-id";
      description
        "datacenter identifier";
      uses datacenter {
        description
          "The datacanter information";
      }
    }
    reference
      " ";
  }



}
